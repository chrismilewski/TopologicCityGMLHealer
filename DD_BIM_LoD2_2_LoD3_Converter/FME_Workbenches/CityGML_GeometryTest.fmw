FME workspace CityGML_GeometryTest.fmw

Parameters:
- SourceDataset_CITYGML = D:\02_Projekte\02_MPSC_digitaler_Starkregenzwilling\gml2sql2gml\sqltest\output\Test_14_Buildings\LoD2_33_412_5652_2_SN_BuildingPreferences.gml   # Source CityGML File(s)
- DestDataset_CITYGML = D:\02_Projekte\02_MPSC_digitaler_Starkregenzwilling\gml2sql2gml\sqltest\output\Test_14_Buildings\LoD2_33_412_5652_2_SN_BuildingPreferences_FME_Healing_Attempt.gml   # Destination CityGML Document

Readers:
- CITYGML_2: CITYGML from $(SourceDataset_CITYGML)

Writers:
- CITYGML_1: CITYGML to $(DestDataset_CITYGML)

CityGMLGeometrySetter
    GEOM = lod2MultiSurface
    ROLE = boundedBy
    -> RoofSurface (writer CITYGML_1)
RoofSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, citygml_function xml_buffer, citygml_roof_type xml_buffer, citygml_measured_height xml_real64, citygml_measured_height_units xml_buffer, citygml_storeys_above_ground xml_uint64, citygml_storeys_below_ground xml_uint64,
      citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer, H_DGM xml_buffer, MaxHBuilding xml_buffer, MaxZBuilding xml_buffer, OBJEKT_ID xml_buffer, confidence xml_buffer, sst xml_buffer, gml_parent_id_building xml_buffer, BldgPartID xml_buffer, DoorCount xml_buffer, Innenwand xml_buffer, WindowPreference xml_buffer, Z_Differenz xml_buffer, Z_Fenster xml_buffer, _issues{}.count xml_uint32, _issues{}.issue_found xml_buffer, _issues{}.location_sample.x xml_real64, _issues{}.location_sample.y xml_real64, _issues{}.location_sample.z xml_real64
CityGMLGeometrySetter_2
    GEOM = lod2MultiSurface
    ROLE = boundedBy
    -> WallSurface (writer CITYGML_1)
WallSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, citygml_function xml_buffer, citygml_roof_type xml_buffer, citygml_measured_height xml_real64, citygml_measured_height_units xml_buffer, citygml_storeys_above_ground xml_uint64, citygml_storeys_below_ground xml_uint64,
      citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer, H_DGM xml_buffer, MaxHBuilding xml_buffer, MaxZBuilding xml_buffer, OBJEKT_ID xml_buffer, confidence xml_buffer, sst xml_buffer, gml_parent_id_building xml_buffer, BldgPartID xml_buffer, DoorCount xml_buffer, Innenwand xml_buffer, WindowPreference xml_buffer, Z_Differenz xml_buffer, Z_Fenster xml_buffer, _issues{}.count xml_uint32, _issues{}.issue_found xml_buffer, _issues{}.location_sample.x xml_real64, _issues{}.location_sample.y xml_real64, _issues{}.location_sample.z xml_real64
CityGMLGeometrySetter_3
    GEOM = lod2MultiSurface
    ROLE = boundedBy
    -> GroundSurface (writer CITYGML_1)
GroundSurface (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, citygml_function xml_buffer, citygml_roof_type xml_buffer, citygml_measured_height xml_real64, citygml_measured_height_units xml_buffer, citygml_storeys_above_ground xml_uint64, citygml_storeys_below_ground xml_uint64,
      citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer, H_DGM xml_buffer, MaxHBuilding xml_buffer, MaxZBuilding xml_buffer, OBJEKT_ID xml_buffer, confidence xml_buffer, sst xml_buffer, gml_parent_id_building xml_buffer, BldgPartID xml_buffer, DoorCount xml_buffer, Innenwand xml_buffer, WindowPreference xml_buffer, Z_Differenz xml_buffer, Z_Fenster xml_buffer, _issues{}.count xml_uint32, _issues{}.issue_found xml_buffer, _issues{}.location_sample.x xml_real64, _issues{}.location_sample.y xml_real64, _issues{}.location_sample.z xml_real64
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
CityGMLGeometrySetter_4
    GEOM = lod2Solid
    ROLE = consistsOfBuildingPart
    -> BuildingPart (writer CITYGML_1)
BuildingPart (writer CITYGML_1)
    attributes: citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, citygml_function xml_buffer, citygml_roof_type xml_buffer, citygml_measured_height xml_real64, citygml_measured_height_units xml_buffer, citygml_storeys_above_ground xml_uint64, citygml_storeys_below_ground xml_uint64,
      citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer, Gemeindeschluessel xml_buffer, Geometrietyp2DReferenz xml_buffer, H_DGM xml_buffer, MaxHBuilding xml_buffer, MaxZBuilding xml_buffer, OBJEKT_ID xml_buffer, confidence xml_buffer, sst xml_buffer, DoorCount xml_buffer, Innenwand xml_buffer, WindowPreference xml_buffer, Z_Differenz xml_buffer, Z_Fenster xml_buffer, _issues{}.count xml_uint32, _issues{}.issue_found xml_buffer, _issues{}.location_sample.x xml_real64, _issues{}.location_sample.y xml_real64, _issues{}.location_sample.z xml_real64
CityGMLGeometrySetter_5
    GEOM = lod2Geometry
    ROLE = cityObjectMember
    -> AttributeCreator
AttributeCreator
    ATTR_TABLE = SET_TO name (varchar(4)) = test
    INPUT_PORT_CONNECTED = CONNECTED
    -> Building (writer CITYGML_1)
Building (writer CITYGML_1)
    attributes: name xml_char(4), citygml_feature_role xml_buffer, citygml_target_uri xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer, citygml_function xml_buffer, citygml_roof_type xml_buffer, citygml_measured_height xml_real64, citygml_measured_height_units xml_buffer, citygml_storeys_above_ground xml_uint64,
      citygml_storeys_below_ground xml_uint64, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer, Gemeindeschluessel xml_buffer, Geometrietyp2DReferenz xml_buffer, H_DGM xml_buffer, MaxHBuilding xml_buffer, MaxZBuilding xml_buffer, OBJEKT_ID xml_buffer, confidence xml_buffer, sst xml_buffer, DoorCount xml_buffer, Innenwand xml_buffer, WindowPreference xml_buffer, Z_Differenz xml_buffer, Z_Fenster xml_buffer, _issues{}.count xml_uint32, _issues{}.issue_found xml_buffer, _issues{}.location_sample.x xml_real64, _issues{}.location_sample.y xml_real64, _issues{}.location_sample.z xml_real64, gml_parent_id_building xml_buffer
Address (reader CITYGML_2)
    attributes: citygml_target_uri xml_buffer, citygml_feature_role xml_buffer, citygml_feature_role_attr_name xml_buffer, citygml_feature_role_attr_val xml_buffer, gml_description xml_buffer, gml_name xml_buffer, citygml_address xml_xml
    -> Address (writer CITYGML_1)
Address (writer CITYGML_1)
    attributes: citygml_target_uri xml_buffer, citygml_feature_role xml_buffer, citygml_feature_role_attr_name xml_buffer, citygml_feature_role_attr_val xml_buffer, gml_description xml_buffer, gml_name xml_buffer, citygml_address xml_xml
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
    -> CityModel (writer CITYGML_1)
CityModel (writer CITYGML_1)
    attributes: citygml_target_uri xml_buffer, gml_description xml_buffer, gml_name xml_buffer, citygml_city_object_member{}.xlink_href xml_buffer, citygml_appearance_member{}.xlink_href xml_buffer, gml_feature_member{}.xlink_href xml_buffer

Bookmark: Planarität etc.
BuildingPart (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, BldgPartID xml_buffer, DatenquelleBodenhoehe xml_buffer, DatenquelleDachhoehe xml_buffer, DatenquelleGeschossanzahl xml_buffer, DatenquelleLage xml_buffer, Grundrissaktualitaet xml_buffer
    -> B_Parts_mit_sst [REQUESTOR]
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_function xml_buffer, citygml_roof_type xml_buffer, citygml_measured_height xml_real64, citygml_measured_height_units xml_buffer, citygml_storeys_above_ground xml_uint64, citygml_storeys_below_ground xml_uint64, citygml_level_of_detail{} xml_buffer, citygml_outer_building_installation{}.xlink_href xml_buffer, citygml_bounded_by{}.xlink_href xml_buffer, citygml_consists_of_building_part{}.xlink_href xml_buffer, citygml_address{}.xlink_href xml_buffer, DatenquelleBodenhoehe xml_buffer, DatenquelleDachhoehe xml_buffer, DatenquelleGeschossanzahl xml_buffer, DatenquelleLage xml_buffer, Gemeindeschluessel xml_buffer, Geometrietyp2DReferenz xml_buffer, Grundrissaktualitaet xml_buffer,
      H_DGM xml_buffer, MaxHBuilding xml_buffer, MaxZBuilding xml_buffer, OBJEKT_ID xml_buffer, confidence xml_buffer, sst xml_buffer
    -> Buildings_mit_sst
Buildings_mit_sst: TestFilter
    DEFAULT_VALUE = <UNFILTERED>
    PASSED_TEST_GROUP_OUTPUT = FIRST
    TEST_LIST = "BOOL_OP,OR,COMPOSITE_TEST,""""""1"""""",TEST_CLAUSE,TEST sst ATTRIBUTE_HAS_A_VALUE """,sst ATTRIBUTE_HAS_A_VALUE
    sst ATTRIBUTE_HAS_A_VALUE -> Junction
    sst ATTRIBUTE_HAS_A_VALUE -> B_Parts_mit_sst [SUPPLIER]
B_Parts_mit_sst: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCopier
AttributeCopier
    ATTR_TABLE = COPY gml_parent_id > gml_parent_id_building
    MISSING_INPUT_ATTRS = REMOVE
    -> Junction
Note: Building & B_Parts mit sst
Junction
    -> RoofSurface_mit_sst [SUPPLIER]
    -> WallSurface_mit_sst [SUPPLIER]
    -> GroundSurface_mit_sst [SUPPLIER]
    -> GeometryValidator_2
RoofSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, FACEAREA xml_buffer, NORMAL_AZI xml_buffer, NORMAL_H xml_buffer, STRUKTUR xml_buffer, Z_MAX_ASL xml_buffer, Z_MIN_ASL xml_buffer, Z_Max xml_buffer, Z_Min xml_buffer
    -> RoofSurface_mit_sst [REQUESTOR]
RoofSurface_mit_sst: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter
    MERGED -> Junction_2
WallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, DachName_LOD2 xml_buffer, DachTyp_LOD2 xml_buffer, DoorCount xml_buffer, FACEAREA xml_buffer, Innenwand xml_buffer, NORMAL_AZI xml_buffer, NORMAL_H xml_buffer, STRUKTUR xml_buffer, WindowPreference xml_buffer, Z_Differenz xml_buffer, Z_Fenster xml_buffer, Z_MAX_ASL xml_buffer, Z_MIN_ASL xml_buffer, Z_Max xml_buffer, Z_Min xml_buffer
    -> WallSurface_mit_sst [REQUESTOR]
WallSurface_mit_sst: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter_2
    MERGED -> Junction_2
GroundSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_level_of_detail{} xml_buffer, BldgFaceID xml_buffer, FACEAREA xml_buffer, STRUKTUR xml_buffer, Z_MIN_ASL xml_buffer, Z_Min xml_buffer
    -> GroundSurface_mit_sst [REQUESTOR]
GroundSurface_mit_sst: FeatureMerger
    ATTR_ACCUM_MODE = Merge Supplier
    ATTR_CONFLICT_RES_LOOKUP = REQUESTOR_IF_CONFLICT
    IGNORE_NULLS = No
    JOIN_KEYS = @Value(gml_parent_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PlanarityFilter_3
    MERGED -> Junction_2
Note: all_Surfaces
Junction_2
    -> GeometryValidator_3
    -> GeometryValidator_4
GeometryValidator_3
    ISSUE_ATTR_NAME = _issues
    PRESETS = Custom
    REPAIR = NO
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE TYPE_REPAIR CONNECT_Z_MODE]FIRST_WINS]ARC_ENDPOINT_TOLERANCE_MODE]Auto]ARC_ENDPOINT_TOLERANCE]<Unused>]FME_CONTROLLER_QUERY_FILE]]FME_CONTROLLER_CHOICE]TYPE_REPAIR
    SUMMARY = DETAILED_SUMMARY
    ISSUE_LOCATIONS -> TestFilter
TestFilter
    DEFAULT_VALUE = <UNFILTERED>
    PASSED_TEST_GROUP_OUTPUT = FIRST
    TEST_LIST = "BOOL_OP,OR,COMPOSITE_TEST,""""""1"""""",TEST_CLAUSE,TEST @Value(issue_found) = Self-Intersections in 2D",Self-Intersections in 2D,"BOOL_OP,OR,COMPOSITE_TEST,""""""1"""""",TEST_CLAUSE,TEST @Value(issue_found) = Invalid Solid Boundaries",Invalid Solid Boundaries,"BOOL_OP,OR,COMPOSITE_TEST,""""""1"""""",TEST_CLAUSE,TEST @Value(issue_found) = Duplicate Consecutive Points in 3D",Duplicate Consecutive Points,"BOOL_OP,OR,COMPOSITE_TEST,""""""1"""""",TEST_CLAUSE,TEST @Value(issue_found) = Non-Planar Surfaces",Non-Planar Surfaces
    Non-Planar Surfaces -> Gruppieren_nach_gml_id_2
Gruppieren_nach_gml_id_2: Aggregator
    ACCUM_ATTRS = None
    AGGREGATE_TYPE = Homogeneous Collection (If Possible)
    GROUP_BY = gml_parent_id
    MODE = Geometry - Assemble One Level
    SEP = ,
    AGGREGATE -> non_planar_Buildings_2
non_planar_Buildings_2: Tester
    BOOL_OP = OR
    TEST_CLAUSE = CASE_INSENSITIVE_TEST @Value(gml_parent_id) BEGINS_WITH Part
    TEST_MODE = CASE_INSENSITIVE_TEST
TestFilter_4
    DEFAULT_VALUE = <UNFILTERED>
    PASSED_TEST_GROUP_OUTPUT = FIRST
    TEST_LIST = "BOOL_OP,OR,COMPOSITE_TEST,""""""1"""""",TEST_CLAUSE,TEST @Value(gml_id) = Face_0015FXN_0_7",Aggregate
    Aggregate -> Deaggregator
    <UNFILTERED> -> CityGMLGeometrySetter_3

Bookmark: Wasserdichte
GeometryValidator_2
    ISSUE_ATTR_NAME = _issues
    PRESETS = Custom
    REPAIR = NO
    RULES = SOLID_VOID_REPAIR FME_CONTROLLER_QUERY_FILE]]FME_CONTROLLER_CHOICE]SOLID_VOID_REPAIR SHELL_VALIDATION FLIP_APPEARANCE_MODE]FLIP_APPEARANCES]FME_CONTROLLER_QUERY_FILE]transformers/dependencies/geometryvalidator9/SHELL_VALIDATION.fme]FME_CONTROLLER_CHOICE]SHELL_VALIDATION SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION
    SUMMARY = DETAILED_SUMMARY
    ISSUE_LOCATIONS -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(issue_found) = Invalid Solid Boundaries",Invalid Solid Boundaries,"BOOL_OP,OR,COMPOSITE_TEST,""""""1"""""",TEST_CLAUSE,TEST @Value(issue_found) = Incorrect Solid Orientation",Incorrect Solid Orientation
    Invalid Solid Boundaries -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(details) = Surface Not Closed",Surface Not Closed,"BOOL_OP,OR,COMPOSITE_TEST,""""""1"""""",TEST_CLAUSE,TEST @Value(details) = Surface Self Intersects",Surface Self Intersects,"BOOL_OP,OR,COMPOSITE_TEST,""""""1"""""",TEST_CLAUSE,TEST @Value(details) = Not Valid 2-Manifold",Not Valid 2-Manifold,"BOOL_OP,OR,COMPOSITE_TEST,""""""1"""""",TEST_CLAUSE,TEST @Value(details) = Face Wrong Orientation",Face Wrong Orientation

Bookmark: Planarität
PlanarityFilter
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id
PlanarityFilter_2
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id
PlanarityFilter_3
    ANGULAR_TOLERANCE_CHOICE_LOOKUP = AUTO
    OUTPUT_LOOKUP = EXPOSE_SURFACE_NORMAL
    THICKNESS_TOLERANCE = 0.00141
    THICKNESS_TOLERANCE_CHOICE_LOOKUP = CUSTOM
    ANGULAR_TOLERANCE_CHOICE = Automatic
    OUTPUT_NORMAL = Yes
    THICKNESS_TOLERANCE_CHOICE = Custom
    NOT_PLANAR -> Gruppieren_nach_gml_id

Bookmark: Repair_Attempt
GeometryValidator_4
    ISSUE_ATTR_NAME = _issues
    PRESETS = Custom
    REPAIR = YES
    RULES = CONSECUTIVE_IDENTICAL_VERTICES_2D CHECK_Z]YES]TOLERANCE]0.00173]FME_CONTROLLER_QUERY_FILE]]FME_CONTROLLER_CHOICE]CONSECUTIVE_IDENTICAL_VERTICES_2D SELF_INTERSECTING CHECK_HOLE_TOUCHING_POLYGON]No]CONNECT_Z_MODE_SI]FIRST_WINS]SELF_INTERSECTION_TOLERANCE]Automatic]VALIDATE_CURVES_POINTS]Yes]INTERSECT_ACROSS_MULTIS]No]FME_CONTROLLER_QUERY_FILE]]FME_CONTROLLER_CHOICE]SELF_INTERSECTING SHELL_VALIDATION FLIP_APPEARANCE_MODE]FLIP_APPEARANCES]FME_CONTROLLER_QUERY_FILE]]FME_CONTROLLER_CHOICE]SHELL_VALIDATION PLANAR_SURFACE CHECK_AREA]DO_NOT_CHECK_AREA]TOLERANCE_MODE]CUSTOM]TOLERANCE]0.00141]ANGULAR_TOLERANCE_MODE]AUTO]ANGULAR_TOLERANCE]<Unused>]FME_CONTROLLER_QUERY_FILE]]FME_CONTROLLER_CHOICE]PLANAR_SURFACE SOLID_VOID_REPAIR FME_CONTROLLER_QUERY_FILE]]FME_CONTROLLER_CHOICE]SOLID_VOID_REPAIR SURFACE_ORIENTATION FME_CONTROLLER_QUERY_FILE]]FME_CONTROLLER_CHOICE]SURFACE_ORIENTATION SOLID_ORIENTATION FME_CONTROLLER_QUERY_FILE]]FME_CONTROLLER_CHOICE]SOLID_ORIENTATION AREA_ORIENTATION AREA_ORIENTATION]VALID]FME_CONTROLLER_QUERY_FILE]]FME_CONTROLLER_CHOICE]AREA_ORIENTATION TYPE_REPAIR CONNECT_Z_MODE]FIRST_WINS]ARC_ENDPOINT_TOLERANCE_MODE]Custom]ARC_ENDPOINT_TOLERANCE]0.00141]FME_CONTROLLER_QUERY_FILE]]FME_CONTROLLER_CHOICE]TYPE_REPAIR
    SUMMARY = DETAILED_SUMMARY
    PASSED -> Junction_3
    REPAIRED -> Junction_3
Junction_3
    -> Type
    -> BuildinPart_or_Building
Type: TestFilter
    DEFAULT_VALUE = <UNFILTERED>
    PASSED_TEST_GROUP_OUTPUT = FIRST
    TEST_LIST = "BOOL_OP,OR,COMPOSITE_TEST,""""""1"""""",TEST_CLAUSE,TEST @Value(STRUKTUR) = Dach",RoofSurface,"BOOL_OP,OR,COMPOSITE_TEST,""""""1"""""",TEST_CLAUSE,TEST @Value(STRUKTUR) = Wand",WallSurface,"BOOL_OP,OR,COMPOSITE_TEST,""""""1"""""",TEST_CLAUSE,TEST @Value(STRUKTUR) = Boden",GroundSurface
    RoofSurface -> CityGMLGeometrySetter
    WallSurface -> CityGMLGeometrySetter_2
    GroundSurface -> TestFilter_4
BuildinPart_or_Building: TestFilter
    DEFAULT_VALUE = Building
    PASSED_TEST_GROUP_OUTPUT = FIRST
    TEST_LIST = "BOOL_OP,OR,COMPOSITE_TEST,""""""1"""""",TEST_CLAUSE,CASE_INSENSITIVE_TEST @Value(gml_parent_id) BEGINS_WITH Part",BuildingPart
    BuildingPart -> BuildingPart
    Building -> Building
BuildingPart: Aggregator
    ACCUM_ATTRS = All
    GROUP_BY = gml_parent_id
    MODE = Attributes Only
    SEP = ,
    AGGREGATE -> Building_2
    AGGREGATE -> AttributeManager_3
AttributeManager_3
    ATTR_TABLE = REMOVE gml_id (buffer)
    -> AttributeRenamer_3
AttributeRenamer_3
    ATTR_TABLE:
      RENAME_SET_DEFAULT gml_parent_id > gml_id
      RENAME_SET_DEFAULT gml_parent_id_building > gml_parent_id
    KEEP_RENAMED_ONLY = no
    MISSING_INPUT_ATTRS = REMOVE
    -> CityGMLGeometrySetter_4
Building_2: Aggregator
    ACCUM_ATTRS = All
    GROUP_BY = gml_parent_id_building
    MODE = Attributes Only
    SEP = ,
    AGGREGATE -> AttributeManager_2
AttributeManager_2
    ATTR_TABLE:
      REMOVE gml_parent_id (buffer)
      REMOVE gml_id (buffer)
    -> AttributeRenamer_2
AttributeRenamer_2
    ATTR_TABLE = RENAME_SET_DEFAULT gml_parent_id_building > gml_parent_id
    KEEP_RENAMED_ONLY = no
    MISSING_INPUT_ATTRS = REMOVE
    -> Junction_4
Building: Aggregator
    ACCUM_ATTRS = All
    GROUP_BY = gml_parent_id
    MODE = Attributes Only
    SEP = ,
    AGGREGATE -> Junction_4
Junction_4
    -> AttributeManager
AttributeManager
    ATTR_TABLE = REMOVE gml_id (buffer)
    -> AttributeRenamer
AttributeRenamer
    ATTR_TABLE = RENAME_SET_DEFAULT gml_parent_id > gml_id
    KEEP_RENAMED_ONLY = no
    MISSING_INPUT_ATTRS = REMOVE
    -> CityGMLGeometrySetter_5

Bookmark: fehlerhafte Gebäude (Planarität)
Gruppieren_nach_gml_id: Aggregator
    ACCUM_ATTRS = None
    AGGREGATE_TYPE = Homogeneous Collection (If Possible)
    GROUP_BY = gml_parent_id
    MODE = Geometry - Assemble One Level
    SEP = ,
    AGGREGATE -> non_planar_Buildings
non_planar_Buildings: Tester
    BOOL_OP = OR
    TEST_CLAUSE = CASE_INSENSITIVE_TEST @Value(gml_parent_id) BEGINS_WITH Part
    TEST_MODE = CASE_INSENSITIVE_TEST
